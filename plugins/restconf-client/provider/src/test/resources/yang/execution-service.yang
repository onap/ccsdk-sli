module execution-service {
    yang-version 1.1;
    namespace "cds:workflow:rest";
    prefix "cds";

    revision "2019-05-21";

    container process {
        container commonHeader {
            leaf originatorId {
                type string;
            }
            leaf requestId {
                type string;
            }
            leaf subRequestId {
                type string;
            }
        }
        container actionIdentifiers {
            leaf blueprintName {
                type string;
            }
            leaf blueprintVersion {
                type string;
            }
            leaf actionName {
                type string;
            }
            leaf mode {
                type string;
            }
        }
        container payload {
            leaf-list template-prefix {
                type string;
            }
            container resource-assignment-request {
                anyxml resource-assignment-properties;
            }
        }
    }
}
